-- **********************************************
-- Zyxel Communications Corporation
--
-- Enterprise Solution MIB definitions
-- RF MANAGEMENT MIBs
--
-- Copyright by Zyxel Communications Corp.
-- All rights reserved.
-- **********************************************

ZYXEL-ES-RF-MANAGEMENT DEFINITIONS ::= BEGIN

IMPORTS

	MODULE-IDENTITY,
	OBJECT-IDENTITY,
	OBJECT-TYPE			FROM SNMPv2-SMI

	OBJECT-GROUP,
	MODULE-COMPLIANCE	FROM SNMPv2-CONF

	esMgmt				FROM ZYXEL-ES-SMI;


--
-- Node: esRFMgmt
--

esRFMgmt MODULE-IDENTITY
	LAST-UPDATED		"201009200000Z"
	ORGANIZATION	"Enterprise Solution Zyxel"
	CONTACT-INFO		""
	DESCRIPTION
		"The sub tree for RF management information"
	::= { esMgmt 6 }

rfMgmtInfo			OBJECT-IDENTITY
	STATUS		current
	DESCRIPTION
		"The subtree for CAPWAP"
	::= { esRFMgmt 2 }
	
rfMgmtUnClassAP OBJECT-TYPE
	SYNTAX	  Unsigned32
	MAX-ACCESS  read-only
	STATUS	current
	DESCRIPTION
		"Total Un-Classified APs."
	::= { rfMgmtInfo 1 }


rfMgmtRogueAP OBJECT-TYPE
	SYNTAX	  Unsigned32
	MAX-ACCESS  read-only
	STATUS	current
	DESCRIPTION
		"Total Rogue APs."
	::= { rfMgmtInfo 2 }


rfMgmtFriendlyAP OBJECT-TYPE
	SYNTAX	  Unsigned32
	MAX-ACCESS  read-only
	STATUS	current
	DESCRIPTION
		"Total Friendly APs."
	::= { rfMgmtInfo 3 }
                              
END
