-- **********************************************
-- Zyxel Communications Corporation
--
-- Enterprise Solution MIB definitions
-- WIRELESS MIBs (WIRELESS)
--
-- Copyright by Zyxel Communications Corp.
-- All rights reserved.
-- **********************************************

ZYXEL-ES-WIRELESS DEFINITIONS ::= BEGIN

IMPORTS

	MODULE-IDENTITY,
	OBJECT-IDENTITY,
	OBJECT-TYPE			FROM SNMPv2-SMI

	OBJECT-GROUP,
	MODULE-COMPLIANCE	FROM SNMPv2-CONF

	DisplayString, MacAddress, DateAndTime	FROM SNMPv2-TC

	esMgmt				FROM ZYXEL-ES-SMI;


--
-- Node: esWireless
-- includes wlanRadioTable, wlanStationTable, wlanStatisticsTable, wlanTraps
--

esWireless MODULE-IDENTITY
	LAST-UPDATED		"201503230000Z"
	ORGANIZATION	"Enterprise Solution Zyxel"
	CONTACT-INFO		""
	DESCRIPTION
		"The sub tree for Wireless information"
	::= { esMgmt 5 }


--
-- Node: wlanControllerAPTable
--

wlanControllerAPTable OBJECT-TYPE
        SYNTAX		SEQUENCE OF WlanControllerAPEntry
        MAX-ACCESS	not-accessible
        STATUS		current
        DESCRIPTION
		"This table lists Controller APs information. Use managmented AP number as the index of each entry"
        ::= { esWireless 11 }

wlanControllerAPEntry OBJECT-TYPE
        SYNTAX		WlanControllerAPEntry
        MAX-ACCESS	not-accessible
        STATUS		current
        DESCRIPTION
		"An entry describing wireless information for each managmented AP."
        INDEX {wlanControllerAPIndex }
        ::= {  wlanControllerAPTable 1 }

WlanControllerAPEntry ::= SEQUENCE {  
	wlanControllerAPIndex Integer32,
	wlanControllerAPMac	OCTET STRING,	
	wlanControllerAPDescription	OCTET STRING,
	wlanControllerAPMgmtIPAddr		IpAddress,
	wlanControllerAPStationNum			Unsigned32,	 
	wlanControllerAPState			INTEGER,
	wlanControllerAPTx				Counter64,
	wlanControllerAPRx				Counter64,
	}
	wlanControllerAPIndex OBJECT-TYPE
	        SYNTAX		Integer32 (1..65535)           
	        MAX-ACCESS	read-only
	        STATUS		current
	        DESCRIPTION
			"AP index."	  
			::= { wlanControllerAPEntry 1 }

	wlanControllerAPMac OBJECT-TYPE
	        SYNTAX		OCTET STRING             
	        MAX-ACCESS	read-only
	        STATUS		current
	        DESCRIPTION
			"The MAC Addresss of the AP."
	        DEFVAL { "public" }
	        ::= { wlanControllerAPEntry 2 }

	wlanControllerAPDescription OBJECT-TYPE
	 		SYNTAX		OCTET STRING
	        MAX-ACCESS	read-only
	        STATUS		current
	        DESCRIPTION
			"The total numbers of associated stations"
	        ::= { wlanControllerAPEntry 3 }

	wlanControllerAPMgmtIPAddr OBJECT-TYPE
	 		SYNTAX		IpAddress
	        MAX-ACCESS	read-only
	        STATUS		current
	        DESCRIPTION
			"AP managmented IP "
	        ::= { wlanControllerAPEntry 4 }

	wlanControllerAPStationNum OBJECT-TYPE
	 	SYNTAX		Unsigned32
	        MAX-ACCESS	read-only
	        STATUS		current
	        DESCRIPTION
			"The total numbers of associated stations"
	        ::= { wlanControllerAPEntry 5 }

	wlanControllerAPState OBJECT-TYPE
	 	SYNTAX		INTEGER {
			offline (0),
			online (1)
		}
	        MAX-ACCESS	read-only
	        STATUS		current
	        DESCRIPTION
			"The status of AP Device"
	        ::= { wlanControllerAPEntry 6 }

	wlanControllerAPTx OBJECT-TYPE
	 	SYNTAX		Counter64
	        MAX-ACCESS	read-only
	        STATUS		current
	        DESCRIPTION
			"The number of bytes transmitted from the AP."
	        ::= { wlanControllerAPEntry 7 }

	wlanControllerAPRx OBJECT-TYPE
	 	SYNTAX		Counter64
	        MAX-ACCESS	read-only
	        STATUS		current
	        DESCRIPTION
			"The number of bytes received by the AP."
	        ::= { wlanControllerAPEntry 8 }
--
-- Node: wlanControllerAPRadio
--

wlanControllerAPRadioTable OBJECT-TYPE
        SYNTAX		SEQUENCE OF WlanControllerAPRadioEntry
        MAX-ACCESS	not-accessible
        STATUS		current
        DESCRIPTION
		"This table lists the AP radio information."
        ::= { esWireless 12 }

wlanControllerAPRadioEntry OBJECT-TYPE
        SYNTAX		WlanControllerAPRadioEntry
        MAX-ACCESS	not-accessible
        STATUS		current
        DESCRIPTION
		"An entry describing WLAN Radio information for each chip."
        INDEX { wlanControllerRadioIndex }

        ::= {  wlanControllerAPRadioTable 1 }

WlanControllerAPRadioEntry ::= SEQUENCE { 
	wlanControllerRadioIndex	Integer32, 
	wlanControllerRadioStationNum		Unsigned32, 
	wlanControllerRadioCurrentChannel	INTEGER,
	wlanControllerRadioOperationMode			INTEGER,
	wlanControllerRadioBand			INTEGER,
	wlanControllerRadioTx			Counter64,
	wlanControllerRadioRx			Counter64,
	wlanControllerRadioTxPower      Integer32,
		}
	wlanControllerRadioIndex OBJECT-TYPE
	        SYNTAX		Integer32 (1..4)           
	        MAX-ACCESS	read-only
	        STATUS		current
	        DESCRIPTION
			"AP radio index."	  
			::= { wlanControllerAPRadioEntry 1 }   
	wlanControllerRadioStationNum OBJECT-TYPE
	 		SYNTAX		Unsigned32
	        MAX-ACCESS	read-only
	        STATUS		current
	        DESCRIPTION
			"The total numbers of associated stations"
	        ::= { wlanControllerAPRadioEntry 2 }

   	wlanControllerRadioCurrentChannel OBJECT-TYPE
 		SYNTAX		INTEGER {
 			device_is_disable(0),
 			channel-01_2412mhz(1),
 			channel-02_2417mhz(2),
 			channel-03_2422mhz(3),
 			channel-04_2427mhz(4),
			channel-05_2432mhz(5),
			channel-06_2437mhz(6),
			channel-07_2442mhz(7),
			channel-08_2447mhz(8),
			channel-09_2452mhz(9),
			channel-10_2457mhz(10),
			channel-11_2462mhz(11),
			channel-12_2467mhz(12),
			channel-13_2472mhz(13),

			channel-36_5180mhz(36),
			channel-40_5200mhz(40),
			channel-44_5220mhz(44),
			channel-48_5240mhz(48),
			channel-52_5260mhz(52),
			channel-56_5280mhz(56),
			channel-60_5300mhz(60),
			channel-64_5320mhz(64),
			channel-100_5500mhz(100),
			channel-104_5520mhz(104),
			channel-108_5540mhz(108),
			channel-112_5560mhz(112),
			channel-116_5580mhz(116),
			channel-120_5600mhz(120),
			channel-124_5620mhz(124),
			channel-128_5640mhz(128),
			channel-132_5660mhz(132),
			channel-136_5680mhz(136),
			channel-140_5700mhz(140),
			channel-149_5745mhz(149),
			channel-153_5765mhz(153),
			channel-157_5785mhz(157),
			channel-161_5805mhz(161),
			channel-165_5825mhz(165)
 		}
	        MAX-ACCESS	read-only
	        STATUS		current
	        DESCRIPTION
			"The current operating wireless channel."
	        ::= { wlanControllerAPRadioEntry 3 }

	    wlanControllerRadioOperationMode OBJECT-TYPE
 		SYNTAX	INTEGER {
 			na(0),
			ap(1), 
 			monitor(2),
 			mesh-Root(3),
 			mesh-repeater(4) 		
 		}
	        MAX-ACCESS	read-only
        STATUS		current
        DESCRIPTION
			"The operation mode of the radio."
	        ::= { wlanControllerAPRadioEntry 4 }

	wlanControllerRadioBand OBJECT-TYPE
	 	SYNTAX		INTEGER { 
	 		na(0),
			mode_2_4G(1),
	 		mode_5G(2)
	}
	        MAX-ACCESS	read-only
	        STATUS		current
	        DESCRIPTION
			"The control for WLAN radio mode."
	        ::= { wlanControllerAPRadioEntry 5 }

	wlanControllerRadioTx OBJECT-TYPE
	 	SYNTAX		Counter64
	        MAX-ACCESS	read-only
	        STATUS		current
	        DESCRIPTION
			"The number of bytes transmitted by the radio."
	        ::= { wlanControllerAPRadioEntry 6 }

	wlanControllerRadioRx OBJECT-TYPE
	 	SYNTAX		Counter64
	        MAX-ACCESS	read-only
	        STATUS		current
	        DESCRIPTION
			"The number of bytes received by the radio."
	        ::= { wlanControllerAPRadioEntry 7 } 
			
	wlanControllerRadioTxPower OBJECT-TYPE
	 	SYNTAX		Integer32
	        MAX-ACCESS	read-only
	        STATUS		current
	        DESCRIPTION
			"The radio's real output power (dBm)"
	        ::= { wlanControllerAPRadioEntry 8 } 
			
--
-- Node: wlanControllerAPMultiVAPTable
--

wlanControllerAPVAPTable OBJECT-TYPE
        SYNTAX		SEQUENCE OF WlanControllerAPVAPEntry
        MAX-ACCESS	not-accessible
        STATUS		current
        DESCRIPTION
		"This table lists the AP VAP information."
        ::= { esWireless 13 }
--
wlanControllerAPVAPEntry OBJECT-TYPE
        SYNTAX		WlanControllerAPVAPEntry
        MAX-ACCESS	not-accessible
        STATUS		current
        DESCRIPTION
		"An entry describing WLAN BSS information for each radio."
        INDEX { wlanControllerRadioVAPIndex }
        ::= {  wlanControllerAPVAPTable 1 }

WlanControllerAPVAPEntry ::= SEQUENCE { 	
	wlanControllerRadioVAPIndex	Integer32,
	wlanControllerRadioVAPSSIDName OCTET STRING,
	wlanControllerRadioVAPVLANID Integer32,
	wlanControllerRadioVAPSecMode OCTET STRING
	}

	wlanControllerRadioVAPIndex OBJECT-TYPE
	        SYNTAX		Integer32 (1..8)           
	        MAX-ACCESS	read-only
	        STATUS		current
	        DESCRIPTION
			"AP radio VAP index."	  
			::= { wlanControllerAPVAPEntry 1 }

	wlanControllerRadioVAPSSIDName OBJECT-TYPE
	 	SYNTAX		OCTET STRING
	        MAX-ACCESS	read-only
	        STATUS		current
	        DESCRIPTION
			"SSID name"
	        ::= { wlanControllerAPVAPEntry 2 }

	wlanControllerRadioVAPVLANID OBJECT-TYPE
	 		SYNTAX		Integer32 (1..4094) 
	        MAX-ACCESS	read-only
	        STATUS		current
	        DESCRIPTION
			"The VAP VLAN ID."
	        ::= { wlanControllerAPVAPEntry 3 }  

	wlanControllerRadioVAPSecMode OBJECT-TYPE
	 		SYNTAX		OCTET STRING 
	        MAX-ACCESS	read-only
	        STATUS		current
	        DESCRIPTION
			"The VAP security mode."
	        ::= { wlanControllerAPVAPEntry 4 }
--
-- Node: wlanControllerStationTable
--
                  
wlanControllerStationTable OBJECT-TYPE
        SYNTAX		SEQUENCE OF WlanControllerStationEntry
        MAX-ACCESS	not-accessible
		STATUS		current
		DESCRIPTION
		"This table lists controller stations list."
        ::= { esWireless 14 }

wlanControllerStationEntry OBJECT-TYPE
        SYNTAX		WlanControllerStationEntry
        MAX-ACCESS	not-accessible
		STATUS		current
		DESCRIPTION
		"An entry describing the station information."
        INDEX { wlanControllerStationIndex  }
        ::= {  wlanControllerStationTable 1 }
                                                      
WlanControllerStationEntry ::= SEQUENCE {
	wlanControllerStationIndex			Integer32,
	wlanControllerStationMacAddress		OCTET STRING,
	wlanControllerStationAssociatedTime	OCTET STRING,
	wlanControllerStationSSID			OCTET STRING,
	wlanControllerStationIPAddr	IpAddress,
	wlanControllerStationAssociatedAPMac	OCTET STRING,	 
	wlanControllerStationSignalStrength	OCTET STRING,
	wlanControllerStationTx				Counter32,
	wlanControllerStationRx				Counter32,
	wlanControllerStationAssociatedAP	OCTET STRING,
 		}

	wlanControllerStationIndex OBJECT-TYPE
	        SYNTAX		Integer32 (1..65535)
	        MAX-ACCESS	read-only
 		STATUS		current
 		DESCRIPTION
			"Index of stations."
	        ::= { wlanControllerStationEntry 1 }

	wlanControllerStationMacAddress OBJECT-TYPE
	        SYNTAX		OCTET STRING             
	        MAX-ACCESS	read-only
	    	STATUS		current
	    	DESCRIPTION
			"The MAC Addresss of the station."
	        DEFVAL { "public" }
	        ::= { wlanControllerStationEntry 2 }

	wlanControllerStationAssociatedTime OBJECT-TYPE
	        SYNTAX		OCTET STRING
	        MAX-ACCESS	read-only
	    	STATUS		current
	    	DESCRIPTION
			"The associated time of the station."
	        ::= { wlanControllerStationEntry 3 }

	wlanControllerStationSSID OBJECT-TYPE
	        SYNTAX		OCTET STRING
	        MAX-ACCESS	read-only
	    	STATUS		current
	    	DESCRIPTION
			"The associated ssid."
	        ::= { wlanControllerStationEntry 4 }   

	wlanControllerStationIPAddr OBJECT-TYPE
	        SYNTAX		IpAddress             
	        MAX-ACCESS	read-only
		STATUS		current
		DESCRIPTION
			"The IP Addresss of the station."
	        ::= { wlanControllerStationEntry 5 }

	wlanControllerStationAssociatedAPMac OBJECT-TYPE
	        SYNTAX		OCTET STRING             
	        MAX-ACCESS	read-only
		STATUS			current
		DESCRIPTION
			"The MAC Addresss of the Associated AP."	
            ::= { wlanControllerStationEntry 6 }

    wlanControllerStationSignalStrength OBJECT-TYPE
	        SYNTAX		OCTET STRING
	        MAX-ACCESS	read-only
		STATUS		current
		DESCRIPTION
			"Stations singal Strength (dbm)"
	        ::= { wlanControllerStationEntry 7 }

	wlanControllerStationTx OBJECT-TYPE
	        SYNTAX		Counter32
	        MAX-ACCESS	read-only
		STATUS		current
		DESCRIPTION
			"Bytes of packets transmitted from the station."
	        ::= { wlanControllerStationEntry 8 }
			
	wlanControllerStationRx OBJECT-TYPE
	        SYNTAX		Counter32
	        MAX-ACCESS	read-only
		STATUS		current
		DESCRIPTION
			"Bytes of packets received by the station."
	        ::= { wlanControllerStationEntry 9 }
			
	wlanControllerStationAssociatedAP OBJECT-TYPE
	        SYNTAX		OCTET STRING
	        MAX-ACCESS	read-only
	    	STATUS		current
	    	DESCRIPTION
			"This indicates the AP through which the station is connected to the network."
	        ::= { wlanControllerStationEntry 10 }

END
