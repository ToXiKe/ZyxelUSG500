-- **********************************************
-- Zyxel Communications Corporation
--
-- Enterprise Solution MIB definitions
-- Zyxel AP Management MIBs 
--
-- LiKuang Tsai
--
-- Copyright by Zyxel Communications Corp.
-- All rights reserved.
-- **********************************************

ZYXEL-ES-ZyxelAPMgmt DEFINITIONS ::= BEGIN

IMPORTS

	MODULE-IDENTITY,
	OBJECT-IDENTITY,
	OBJECT-TYPE		FROM SNMPv2-SMI

	OBJECT-GROUP,
	MODULE-COMPLIANCE	FROM SNMPv2-CONF

	esMgmt			FROM ZYXEL-ES-SMI;

zyxelAPMgmt MODULE-IDENTITY
	LAST-UPDATED	"201403100000Z"    
	ORGANIZATION "Enterprise Solution Zyxel"     
	CONTACT-INFO
		""	   
	DESCRIPTION
		"The subtree for zyxelAPMgmt information"
	::= { esMgmt 4 }


-- zyxelAPMgmt OIDs
                                    
	
	operationMode OBJECT-TYPE
		SYNTAX	  INTEGER  {
			standalone (1),
    		controller (2),
    		managed (3)
		}
		MAX-ACCESS  read-only
		STATUS  current
		DESCRIPTION
			"Wireless AP operation mode"
	::= { zyxelAPMgmt 1 } 	
                                 	                           
	wlanAPTx OBJECT-TYPE
		SYNTAX		Counter64
		MAX-ACCESS	read-only
		STATUS		current
		DESCRIPTION
			"AP TX bytes"
	::= { zyxelAPMgmt 2 }
	
	wlanAPRx OBJECT-TYPE
		SYNTAX		Counter64
		MAX-ACCESS	read-only
		STATUS		current
		DESCRIPTION
			"AP RX bytes"
	::= { zyxelAPMgmt 3 }
	
	
END
